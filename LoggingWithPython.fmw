FME workspace LoggingWithPython.fmw
Title: LoggingWithPython
Description: This workspace is an example of how to read the Log in "Real-Time" as it is a very nuanced use-case.
Learn about other use-cases here: How to extract and use log information in Workbench – FME Support Center
Created by Gavin Jeter, LOCUS
History: 2025-04-03,G Jeter,Initial Creation
Startup Python:
      # Startup Python

      import fmeobjects

      # create log file object
      log = fmeobjects.FMELogFile()

      # initialize flag
      logReport = 0

      # define callback function to be run on every log message
      def logReporting(severity,message):
         # import flag
         global logReport
         # set flag if triggered
         if "LogReporting" in message:
            logReport = message

      # set logfile callback function
      log.setCallBack(logReporting)
Shutdown Python:
      # Shutdown Python

      # dispose of log object (needed since Python API wraps C++)
      log = None

Note: Learn about more use-cases here: How to extract and use log information in Workbench – FME Support Center

Bookmark: Gavin's Original Purpose - In-flight Log Reporting
Creator
    GEOMTYPE = Geometry Object
    NUM = 1
    CREATED -> FeatureMerger [REQUESTOR]
Creator_2
    GEOMTYPE = Geometry Object
    NUM = 1
    CREATED -> Cloner
Cloner
    COPIES = 5
    COPYATT = _copynum
    COPY -> FeatureMerger [SUPPLIER]
FeatureMerger
    ATTR_ACCUM_MODE = Merge Supplier
    ATTR_CONFLICT_RES_LOOKUP = REQUESTOR_IF_CONFLICT
    IGNORE_NULLS = No
    JOIN_KEYS = @Value(_creation_instance) @Value(_creation_instance) AUTO
    MERGE_TYPE = Attributes Only
    PROCESS_DUPS = NO
    REJECT_NULL_MISSING_KEYS = No
    SUPPLIERS_FIRST = No
    ATTR_CONFLICT_RES = Use Requestor
    MERGED -> Logger
    <REJECTED> -> Logger_2
Note: Warning
Logger
    LOG_FEATURE = LOG_ONLY
    MAXCOORDS = 20
    MAXFEATS = 20
    MESSAGE = LogReporting | WARNING | @DateTimeFormat(@ReplaceRegularExpression(@DateTimeNow(UTC),"\.\d+","",caseSensitive=TRUE),ISO) UTC | Message:
    SEVERITY = WARN
    LOGGED -> PythonCaller
Note: Error
Logger_2
    LOG_FEATURE = LOG_ONLY
    MAXCOORDS = 20
    MAXFEATS = 20
    MESSAGE = LogReporting | ERROR | @DateTimeFormat(@ReplaceRegularExpression(@DateTimeNow(UTC),"\.\d+","",caseSensitive=TRUE),ISO) UTC | Message:
    SEVERITY = ERROR
    LOGGED -> PythonCaller
Note: Search for LogReporting in Log
PythonCaller
    NEW_ATTRIBUTES = logMessage buffer
    PYTHONSOURCE:
      import fme
      from fme import BaseTransformer
      import fmeobjects


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              """This method is called for each feature which enters the PythonCaller."""
              global logReport
              # if logMessage exists, write out logReport
              feature.setAttribute('logMessage',logReport)
              self.pyoutput(feature, output_tag="PYOUTPUT")

          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> AttributeSplitter
Note: Split into attributes on Bar
AttributeSplitter
    ATTR_NAME = logMessage
    DELIMITER = |
    DROP_EMPTY_PARTS = NO
    LIST_NAME = _list
    TRIM_TYPE = BOTH
    -> AttributeManager
Note: Attribute Cleanup
AttributeManager
    ATTR_TABLE:
      REMOVE _creation_instance (uint64)
      REMOVE _copynum (uint32)
      REMOVE fme_rejection_code (buffer)
      SET_TO logMessage_type (varchar(200)) = @Value(_list{1})
      SET_TO logMessage_timestamp (varchar(200)) = @Value(_list{2})
      SET_TO logMessage_message (varchar(200)) = @Value(_list{3})
    -> TestFilter
Note: Filter to desired action
TestFilter
    DEFAULT_VALUE = <UNFILTERED>
    PASSED_TEST_GROUP_OUTPUT = FIRST
    TEST_LIST = "BOOL_OP,OR,COMPOSITE_TEST,""""""1"""""",TEST_CLAUSE,TEST @Value(logMessage_type) = WARNING",Warning,"BOOL_OP,OR,COMPOSITE_TEST,""""""1"""""",TEST_CLAUSE,TEST @Value(logMessage_type) = ERROR",Error
    Warning -> Aggregator
    Error -> AttributeCreator_2
    <UNFILTERED> -> AttributeCreator_2
Note: The Aggregator is a "Blocking" transformer, therefore it waits for all the features to arrive before Grouping, then concatenating (with a linebreak) the WARNING logMessage field
Aggregator
    ACCUM_ATTRS_NAME = Drop Incoming Attributes
    AGGREGATE_TYPE = Homogeneous Collection (If Possible)
    CONCAT_ATTRS = logMessage
    MODE = Geometry - Assemble One Level
    SEP = "\n"
    AGGREGATE -> AttributeCreator
Note: Email Subject, Body
AttributeCreator
    ATTR_TABLE:
      SET_TO _subject (varchar(200)) = Warning - $(FME_WORKSPACE_NAME)
      SET_TO _body (varchar(200)) = Email Body to include whatever message you want, but you will definitly want to include the concatenated:

        @Value(logMessage)
    -> Emailer_2
Note: See Other Workspace for configuration
Emailer_2
    BODY = @Value(_body)
    FROM = serviceAccount@yourOrg.com
    SERVICE = Generic SMTP
    SMTP_CONNECTION = HOST;smtp.yourOrg;PORT;25;ENCRYPTION;None;TIMEOUT;60;AUTHENTICATION;NO;USERNAME;<Unused>;PASSWORD;<Unused>;FME_CONTROLLER_QUERY_FILE;dependencies/Generic SMTP.fme;FME_CONTROLLER_CHOICE;Generic SMTP
    SUBJECT = @Value(_subject)
    TO = monitoredInbox@yourOrg.com
Note: Email Subject, Body
AttributeCreator_2
    ATTR_TABLE:
      SET_TO _subject (varchar(200)) = ERROR - $(FME_WORKSPACE_NAME)
      SET_TO _body (varchar(200)) = Email Body to include whatever message you want, but you will definitly want to include some version of the logMessage details

        @Value(logMessage)
    -> Emailer_3
Note: See Other Workspace for configuration
Emailer_3
    BODY = @Value(_body)
    FROM = serviceAccount@yourOrg.com
    SERVICE = Generic SMTP
    SMTP_CONNECTION = HOST;smtp.yourOrg;PORT;25;ENCRYPTION;None;TIMEOUT;60;AUTHENTICATION;NO;USERNAME;<Unused>;PASSWORD;<Unused>;FME_CONTROLLER_QUERY_FILE;dependencies/Generic SMTP.fme;FME_CONTROLLER_CHOICE;Generic SMTP
    SUBJECT = @Value(_subject)
    TO = monitoredInbox@yourOrg.com
    Sent -> Terminator
Note: You want to Kill the workspace immediately if there is an ERROR, but you also want the Email to fire off prior to that, so you get a notification that something went wrong
Terminator
    MESSAGE:
      ****************************

      Translation Terminated

      EMAIL SENT

      @Value(logMessage_message)


      *****************************
